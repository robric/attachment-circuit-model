module example-ac-glue {
  yang-version 1.1;
  namespace "https://example.com/ns/example-ac-glue";
  prefix example-ac-glue;

  import ietf-l3vpn-svc {
    prefix l3vpn-svc;
    reference
      "RFC 8299";
  }
  import ietf-l2vpn-svc {
    prefix l2vpn-svc;
    reference
      "RFC 8466";
  }
  import ietf-l3vpn-ntw {
    prefix l3nm;
    reference
      "RFC 9182";
  }
  import ietf-l2vpn-ntw {
    prefix l2nm;
    reference
      "RFC 9291";
  }
  import ietf-network-slice-service {
    prefix ietf-nss;
  }
  import ietf-ac-svc {
    prefix ac-svc;
  }

  organization
    "Example Org.";
  contact
    "Example contact";
  description
    "This YANG module defines an example of AC extension
     to glue service models to their attachment circuits.";

  revision 2022-11-30 {
    description
      "Initial revision.";
    reference
      "RFC xxxx: A YANG Network Data Model for Attachment Circuits";
  }

grouping ac-glue {
    description
      "A set of AC-related data.";
    leaf-list ac-ref {
      type ac-svc:attachment-circuit-reference;
      description
        "A reference to the AC as exposed at the service that 
         was provisionned using the AC module.";
    }
}


  augment "/l3vpn-svc:l3vpn-svc"
        + "/l3vpn-svc:sites/l3vpn-svc:site"
        + "/l3vpn-svc:site-network-accesses/l3vpn-svc:site-network-access" {
    description
      "Augments VPN network access with AC provisioning details.";

    uses ac-glue;
  }

  augment "/l2vpn-svc:l2vpn-svc"
        + "/l2vpn-svc:sites/l2vpn-svc:site"
        + "/l2vpn-svc:site-network-accesses/l2vpn-svc:site-network-access" {
    description
      "Augments VPN network access with AC provisioning details.";

    uses ac-glue;
  }

  augment "/l3nm:l3vpn-ntw/l3nm:vpn-services/l3nm:vpn-service"
        + "/l3nm:vpn-nodes/l3nm:vpn-node"
        + "/l3nm:vpn-network-accesses/l3nm:vpn-network-access" {
    description
      "Augments VPN network access with AC provisioning details.";

    uses ac-glue;
  }

  augment "/l2nm:l2vpn-ntw/l2nm:vpn-services/l2nm:vpn-service"
        + "/l2nm:vpn-nodes/l2nm:vpn-node"
        + "/l2nm:vpn-network-accesses/l2nm:vpn-network-access" {
    description
      "Augments VPN network access with AC provisioning details.";

    uses ac-glue;
  }

  augment "/ietf-nss:network-slice-services/ietf-nss:slice-service"
        + "/ietf-nss:sdps/ietf-nss:sdp" {
    description
      "Augments VPN network access with AC provisioning details.";

    uses ac-glue;
  }
}
