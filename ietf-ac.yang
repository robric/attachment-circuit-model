module ietf-ac {
  yang-version 1.1;
  namespace "urn:ietf:params:xml:ns:yang:ietf-ac";
  prefix ac;

  organization
    "IETF OPSAWG (Operations and Management Area Working Group)";
  contact
    "WG Web:   <https://datatracker.ietf.org/wg/opsawg/>
     WG List:  <mailto:opsawg@ietf.org>

  Author:   Mohamed Boucadair
            <mailto:mohamed.boucadair@orange.com>
  Author:   Richard Roberts
           <mailto:rroberts@juniper.net>";
     description
       "This YANG module defines a generic YANG model for
        the configuration of attachment circuits.

        Copyright (c) 2022 IETF Trust and the persons identified as
        authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).

        This version of this YANG module is part of RFC xxx; see the
        RFC itself for full legal notices.";

     revision 2022-11-30 {
       description
         "Initial revision.";
       reference
         "RFC xxxx: A YANG Data Model for Attachment Circuits"";
     }
}
